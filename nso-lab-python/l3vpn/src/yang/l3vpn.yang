module l3vpn {
  namespace "http://com/example/l3vpn";
  prefix l3vpn;

  import ietf-inet-types { prefix inet; }
  import tailf-ncs       { prefix ncs; }
  import tailf-common    { prefix tailf; }
  import site            { prefix site; }


  list l3vpn {
    key "vpn-name";

    uses ncs:service-data;
    ncs:servicepoint "l3vpn-servicepoint";

    leaf vpn-name {
      type string;
    }

    container vpn {
    
      leaf vpn-id {
        type uint32;
      }

      leaf vpn-description {
        type string;
      }
      
      leaf customer {
        type leafref {
          path "/ncs:customers/ncs:customer/ncs:id";
        }
      }
    }

    list link {
      key link-name;
      unique "site";

      leaf link-name {
        type string;
      }

      leaf link-id {
        type uint32;
      }

      leaf link-description {
        type string;
      }

      leaf site {
        mandatory true;
        type leafref {
          path "/site:site/site:name";
        }
      }

      leaf bgp {
        type boolean;
      }
      
      leaf vlan {
        type uint32;
      }

      container pe {
        leaf device {
          type leafref {
            path "/ncs:devices/ncs:device/ncs:name";
          }
        }

        leaf interface {
          type string;
        }

        leaf ip {
          type inet:ipv4-address;
        }

        leaf ipv6 {
          type inet:ipv6-address;
        }

        leaf-list static {
          type inet:ip-prefix;
        }

      }

      container ce {
        leaf device {
          type leafref {
            path "/ncs:devices/ncs:device/ncs:name";
          }
        }

        leaf interface {
          type string;
        }

        leaf ip {
          type inet:ipv4-address;
        }
        
        leaf ipv6 {
          type inet:ipv6-address;
        }

        leaf-list static {
          type inet:ip-prefix;
        }

      }
    }
  }
}
